# stakeholder-requirements

## #15: Stakeholder requirements (Container)

### #16: The door control system shall know which doors to open. (Functional)

### #18: The door control system shall be able to open all doors on the left (Functional)

### #19: The door control system shall be able to open all doors on the right (Functional)

### #20: The door control system shall be able to close all doors. (Functional)

### #21: The door control system shall be able to open doors selectively (Functional)

### #22: The door control system shall be able to monitor the door status (Functional)

### #23: The user shall be able to tell the door control system to open a door (Functional)

### #24: The door control system shall not close a door if something is in the way (Functional)

### #25: The maintainer shall be able to maintain update the software (Functional)

### #26: The door control system shall be accessible in the cockpit (Functional)

### #27: The door control system shall have a function to save door errors (Functional)

### #28: The door control system shall be able to lock doors (Functional)

### #29: The door control system shall only update to authentic software (Functional)

## #30: System requirements (Container)

### #32: The door control system shall check door lock status (Functional)

### #34: If the door control system gets told to open a locked door, then the door control system shall keep that door closed (Functional)

### #35: If there is something in the way of a closing door, then the door control system shall open the closing door (Functional)

### #36: When a passenger pushes a open door button, the door control system shall open the corresponding door (Functional)

### #37: If the door motors draws power over its specified power draw, then the door control system shall stop the closing of the door (Functional)

### #38: When a door fails to close, the door control system shall light up the door error light (Functional)

### #39: When a door fails to close, the door control system shall save what door is faulty (Functional)

### #40: When the train operator pushes the close all doors on the left button, the door control system shall close all doors on the left (Functional)

### #41: When the train operator pushes the open all doors on the left, the door control system shall open all doors on the left (Functional)

### #42: When the train operator pushes the close all doors on the right, the door control system shall close all doors on the right (Functional)

### #43: When the train operator pushes the open all doors on the right, the door control system shall open all doors on the right (Functional)

### #44: When the train operator pushes the open doors selectively button, the door control system shall open the doors facing the platform (Functional)

### #45: When a door is open the door control system shall keep the “doors open” light turned on (Functional)

### #46: When all doors are closed the “doors open” light shall turn off the door open light (Functional)

### #47: The door control system shall be accessible with a usb cable (Functional)

### #48: The door control system shall be able to have its software updated (Functional)

### #49: If a non-authentic software update gets uploaded, then the door control system shall reject the software (Functional)

### #50: When a authentic software update gets uploaded, the door control system shall update to that software (Functional)

### #51: When the train operator pushes the lock doors button, the door control system shall lock the doors (Functional)

### #52: If the train is moving, then the door control system shall keep the doors locked (Functional)

### #53: When the train operator pushes the unlock doors button, the door control system shall unlock the doors (Functional)

### #54: If a door is open and the door control system tries to lock the doors, then the door control system does not lock the doors (Functional)

### #55: If the train doors are not set to operational, then the door control system shall not move the doors (Functional)
